import Power::*;

@Sysml2EditorIdentity { id = "00000000-0000-4000-8000-000000000001"; }
package Vehicle {
  @Sysml2EditorIdentity { id = "33333333-3333-4333-8333-333333333333"; }
  part battery : Power::BatteryPack;
}
