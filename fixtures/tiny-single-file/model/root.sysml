@Sysml2EditorIdentity { id = "00000000-0000-4000-8000-000000000001"; }
package Vehicle {
  @Sysml2EditorIdentity { id = "11111111-1111-4111-8111-111111111111"; }
  part def BatteryPack;

  @Sysml2EditorIdentity { id = "22222222-2222-4222-8222-222222222222"; }
  part battery : BatteryPack;
}
